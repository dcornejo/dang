module dangd-reconciliation {
  yang-version 1.1;
  namespace "urn:dangd:reconciliation";
  prefix dr;

  organization "dangd project";
  description
    "Operational evidence for incomplete hardware compensation and provider
     failures observed while constructing the current operational snapshot.
     This module reports uncertainty; it does not assert that a remnant is
     still present after an operator repairs the device outside dangd.";

  revision 2026-08-23 {
    description "Initial hardware reconciliation state.";
  }

  container hardware-reconciliation {
    config false;
    description
      "The last incomplete hardware compensation known to dangd.  A later
       completely successful hardware transaction clears this report.";

    leaf diverged {
      type boolean;
      mandatory true;
      description
        "True when one or more actions could not be compensated and hardware
         may therefore differ from the published running configuration.";
    }

    list remnant {
      key "action-id";
      description
        "One applied action whose rollback failed.  The path identifies the
         intended configuration instance associated with the hardware work.";

      leaf action-id {
        type string;
        description "Transaction-unique action identifier.";
      }
      leaf instance-path {
        type string;
        mandatory true;
        description
          "Canonical schema-aware configuration instance path supplied by the
           plugin when the action was planned.  This is empty for legacy plugin
           ABIs whose single transaction callback cannot identify an action
           path.";
      }
      leaf reason {
        type string;
        mandatory true;
        description "Backend explanation returned by the failed rollback.";
      }
    }

    list configuration-outcome {
      key "provider instance-path";
      description
        "A plugin-reported per-node result from the most recent successful
         hardware transaction. The operational configuration contains the
         reported applied snapshot, never the unapplied requested value.";
      leaf provider { type string; }
      leaf instance-path { type string; }
      leaf disposition {
        type enumeration {
          enum applied;
          enum transformed;
          enum rejected;
          enum delayed;
        }
      }
      leaf reason { type string; }
    }

    list operational-provider-failure {
      key "provider";
      description
        "A callback or instance-validation failure observed while constructing
         the current operational response. The provider's fragment is omitted.";
      leaf provider {
        type string;
        description "Plugin name copied from its host-validated manifest.";
      }
      leaf stage {
        type enumeration {
          enum callback;
          enum validation;
          enum merge;
        }
        mandatory true;
        description "Boundary at which publication failed.";
      }
      leaf instance-path {
        type string;
        description "Best available schema-aware path to invalid data.";
      }
      leaf reason {
        type string;
        mandatory true;
        description "Callback message or instance-validation diagnostic.";
      }
    }
  }
}
