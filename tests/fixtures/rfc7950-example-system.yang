// Copyright 2026 David Cornejo
// SPDX-License-Identifier: Apache-2.0

// Adapted conformance fixture based on RFC 7950 section 4.2.2.5.
module example-system {
  yang-version 1.1;
  namespace "urn:example:system";
  prefix sys;

  revision 2007-06-09;

  container system {
    leaf host-name { type string; }
    leaf-list domain-search { type string; }
    container login {
      leaf message { type string; }
      list user {
        key name;
        leaf name { type string; }
        leaf full-name { type string; }
        leaf class { type string; }
      }
    }
  }
}
